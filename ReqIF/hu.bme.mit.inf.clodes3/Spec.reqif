# Clodes3

# Specification: Specification Document
- Description: Requirements Document

## R1
Munkavégzés produktivitásának maximalizálása

### R2
Légkör optimalizálása

#### R3
Hőmérséklet optimalizálása

##### R5
Aktuális hőmérséklet mérése

###### R7
Külső hőmérséklet megfigyelése

###### R8
Külső forrás (időjárásjelentő) lekérdezése

###### R9
Teremhőmérséklet megfigyelése

###### R10
Hőmérséklet mérése redundánsan

###### R14
Nem megfelelő hőmérséklet jelzése

###### R15
Webes jelzés

###### R16
Fizikai jelzés

###### R19
Azonnali beavatkozási lehetőség

##### R6
Várható hőmérséklet előrejelzése

###### R11
Várható külső hőmérséklet számítása (időjárásjelentő)

###### R12
Várható teremfoglalás számítása

###### R13
Előrejelzés érvényesítése fényérzékeléssel

###### R17
Órarend figyelembe vétele

##### R20
Aktuális teremfoglalás megfigyelése

###### R21
Számítógépek bekapcsolt állapotának észlelése

###### R22
Arcok felismerése kamera segítségével

#### R4
CO^2 szint megfigyelése

##### R18
Kritikus szint figyelése
