# Cloud Based Demonstrator for Smell Sensing Systems

# Specification: Specification Document
- Description: Requirements Document

## R2
Ideálisabb légköri körülményekkel javítsunk a teremben végzett munkavégzés minőségén.

### R4
A légkör minőségét meg kell tudni jósolni

#### R6
Légkör minőségét monitorozni kell

##### R7
Internetes időjárás-szolgáltatást kell használni az időjárási körülmények felméréséhez

##### R8
Szenzorokat kell telepíteni, a légköri körülmények monitorozásához

###### R9
Több szenzornak kell lennie

##### R14
Emberi közbeavatkozással lehetővé kell tenni a kellemetlen légkör jelzését

###### R15
Le kell helyezni egy fizikai gombot

###### R16
Webes felületen lehessen jelezni a kellemetlen légköri körülményeket

#### R10
Tudni kell a terem foglaltságát a légköri körülmények jóslásához

##### R11
Unix szolgáltatásokat kell telepíteni a laborgépekre, hogy lássuk hány működik

##### R12
Kamerával kell megfigyelni a termet, hogy lássuk, hogy hány hallgató van jelen

##### R13
Órarendi adatokból következtethetünk arra, hogy mekkora a foglaltság

### R5
Be kell tudni avatkozni, ha nem jó a légkör

## R3
Hibatűrőnek kell lennie a rendszernek

## R1
